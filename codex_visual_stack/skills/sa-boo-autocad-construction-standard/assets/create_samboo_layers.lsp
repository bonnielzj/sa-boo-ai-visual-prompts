; SA&BOO AutoCAD layer setup generated by sa-boo-autocad-construction-standard
; Load with APPLOAD or paste into AutoCAD command line / MCP execute_lisp.
(defun c:SABOO_LAYERS (/ make-layer)
  (defun make-layer (name color lw ltype plot /)
    (if (not (tblsearch "LTYPE" ltype))
      (command "_.-LINETYPE" "_Load" ltype "acad.lin" ""))
    (if (not (tblsearch "LAYER" name))
      (command "_.-LAYER" "_New" name ""))
    (command "_.-LAYER" "_Color" (itoa color) name "")
    (command "_.-LAYER" "_Ltype" ltype name "")
    (command "_.-LAYER" "_LWeight" lw name "")
    (if (= plot "No")
      (command "_.-LAYER" "_Plot" "No" name "")
      (command "_.-LAYER" "_Plot" "Yes" name ""))
  )
  (make-layer "I-WALL-FULL-N" 7 "0.35" "Continuous" "Yes")
  (make-layer "I-WALL-LITE-N" 8 "0.18" "Continuous" "Yes")
  (make-layer "I-WALL-DEMO-D" 1 "0.18" "DASHED" "Yes")
  (make-layer "I-DOOR-PANL-N" 3 "0.25" "Continuous" "Yes")
  (make-layer "I-DOOR-SWNG-N" 3 "0.13" "Continuous" "Yes")
  (make-layer "I-WIND-GLAZ-N" 4 "0.18" "Continuous" "Yes")
  (make-layer "I-FURN-FIXD-N" 2 "0.25" "Continuous" "Yes")
  (make-layer "I-FURN-LOOS-N" 9 "0.13" "Continuous" "Yes")
  (make-layer "I-FLOR-FINI-N" 6 "0.13" "Continuous" "Yes")
  (make-layer "I-CEIL-EDGE-N" 5 "0.18" "Continuous" "Yes")
  (make-layer "I-CEIL-GRID-N" 8 "0.09" "Continuous" "Yes")
  (make-layer "E-LITE-FIXT-N" 30 "0.18" "Continuous" "Yes")
  (make-layer "E-SWCH-SYMB-N" 30 "0.18" "Continuous" "Yes")
  (make-layer "E-POWR-OUTL-N" 1 "0.18" "Continuous" "Yes")
  (make-layer "P-PLMB-FIXT-N" 140 "0.18" "Continuous" "Yes")
  (make-layer "M-HVAC-DIFF-N" 151 "0.18" "Continuous" "Yes")
  (make-layer "I-HATCH-CUT" 8 "0.09" "Continuous" "Yes")
  (make-layer "I-HATCH-MATL" 9 "0.09" "Continuous" "Yes")
  (make-layer "I-ANNO-DIMS" 2 "0.18" "Continuous" "Yes")
  (make-layer "I-ANNO-TEXT" 7 "0.18" "Continuous" "Yes")
  (make-layer "I-ANNO-LEAD" 2 "0.18" "Continuous" "Yes")
  (make-layer "I-ANNO-TAGS" 4 "0.18" "Continuous" "Yes")
  (make-layer "I-ANNO-SYMB" 4 "0.18" "Continuous" "Yes")
  (make-layer "I-AXIS-GRID" 8 "0.13" "CENTER" "Yes")
  (make-layer "I-REV-CLOUD-RXX" 1 "0.25" "Continuous" "Yes")
  (make-layer "I-REV-DELT-RXX" 1 "0.25" "Continuous" "Yes")
  (make-layer "I-TTLB-LINE" 7 "0.25" "Continuous" "Yes")
  (make-layer "I-TTLB-TEXT" 7 "0.18" "Continuous" "Yes")
  (make-layer "X-BASE-ARCH" 8 "0.09" "Continuous" "Yes")
  (make-layer "X-UNDERLAY" 8 "0.05" "Continuous" "Yes")
  (make-layer "NPLT-GUIDE" 6 "0.05" "Continuous" "No")
  (make-layer "NPLT-VPORT" 6 "0.00" "Continuous" "No")
  (setvar "CELTSCALE" 1)
  (setvar "LTSCALE" 50)
  (setvar "PSLTSCALE" 1)
  (setvar "DIMASSOC" 2)
  (princ "\nSA&BOO layers created/updated. Run REGEN if linetypes need refresh.")
  (princ)
)
(c:SABOO_LAYERS)
